SMCA-MGMT-PG-STATUS-ACTIVITY-MIB DEFINITIONS ::= BEGIN


IMPORTS
    MODULE-IDENTITY, OBJECT-TYPE, Integer32 FROM SNMPv2-SMI
    OBJECT-GROUP                  	    FROM SNMPv2-CONF;

pg-status-activity MODULE-IDENTITY
    LAST-UPDATED "201502230000Z"
   
     
    ORGANIZATION "smca"
    CONTACT-INFO "email: nobody@sanemail.de"
    DESCRIPTION	 "Postgres Server status - mapping of pg_stat_activity view
		  		  one row per server process holding information related to 
		          the current activity of that process, such as state and current query"
    REVISION 	"201502230000Z"
    DESCRIPTION	"First draft"
    ::= { iso(1) org(3) dod(6) internet(1) private(4) enterprises(1) 
	  fourhorsemen(45204) sub(1) smca(1) 
	  management(2) postgres(2) status(1) 2 }

statusTable OBJECT-TYPE 
	SYNTAX SEQUENCE OF StatusEntry 
	MAX-ACCESS not-accessible
	STATUS current
    DESCRIPTION "Status table, contains one entry per backend process"
	::= {pg-status-activity 1}

statusEntry OBJECT-TYPE
	SYNTAX StatusEntry
	MAX-ACCESS not-accessible
	STATUS current
	DESCRIPTION "Status entry, describes the status of a single backend process"
    INDEX { pid }
	::= { statusTable 1}

BackendPid ::= INTEGER (3 .. 65535)

Oid		   		::= INTEGER
Name	   		::= OCTET STRING

RegClass   		::= Oid

DatabaseId 		::= RegClass
DatabaseName	::= Name
UserId			::= Oid
UserName		::= Name


StatusEntry ::=
	SEQUENCE 
	{
		databaseId			DatabaseId,
		databaseName		OCTET STRING,
		pid					BackendPid,
		userId				Integer32,
		userName			OCTET STRING,
		applicationName		OCTET STRING,
		clientAddress		OCTET STRING,
		clientHostname		OCTET STRING,
		clientPort			Integer32,
		backendStart		OCTET STRING,
		transactionStart	OCTET STRING,
		queryStart			OCTET STRING,
		stateChange			OCTET STRING,
		waiting				OCTET STRING,
		state				OCTET STRING,
		query				OCTET STRING
	}

databaseId OBJECT-TYPE
    SYNTAX		DatabaseId
    MAX-ACCESS  read-only
    STATUS	current
    DESCRIPTION "id (a postgres oid) of the database this backend is connected to.
		 this maps to pg_stat_activity/datid"
    ::= { statusEntry  1 }

databaseName OBJECT-TYPE
    SYNTAX	OCTET STRING
    MAX-ACCESS  read-only
    STATUS	current
    DESCRIPTION "name of the database this backend is connected to.
		 this maps to pg_stat_activity/datname"
    ::= { statusEntry  2 }

pid OBJECT-TYPE
    SYNTAX BackendPid
    MAX-ACCESS  read-only
    STATUS	current
    DESCRIPTION "Process id of this backend 
		 this maps to pg_stat_activity/pid"
    ::= { statusEntry  3 }

userId OBJECT-TYPE
    SYNTAX	Integer32
    MAX-ACCESS  read-only
    STATUS	current
    DESCRIPTION "User id (a postgres oid) of the user connected to  this backend 
		 this maps to pg_stat_activity/usesysid"
    ::= { statusEntry  4 }

userName OBJECT-TYPE
    SYNTAX	OCTET STRING
    MAX-ACCESS  read-only
    STATUS	current
    DESCRIPTION "User name of the user connected to  this backend 
		 this maps to pg_stat_activity/name"
    ::= { statusEntry  5 }

applicationName OBJECT-TYPE
    SYNTAX	OCTET STRING
    MAX-ACCESS  read-only
    STATUS	current
    DESCRIPTION "Name of the application connected to  this backend 
		 this maps to pg_stat_activity/application_name"
    ::= { statusEntry  6 }

clientAddress OBJECT-TYPE
    SYNTAX	OCTET STRING
    MAX-ACCESS  read-only
    STATUS	current
    DESCRIPTION "IP address of the client connected to connected to  this backend 
		 If this field is null it indicated either that the client is 
		 connected via a Unix socket on server machine or that this is 
		 an internal process such as autovacuum.
		 this maps to pg_stat_activity/client_addr"
    ::= { statusEntry  7 }

clientHostname OBJECT-TYPE
    SYNTAX	OCTET STRING
    MAX-ACCESS  read-only
    STATUS	current
    DESCRIPTION "Host name of the connected client, as reported by a reverse DNS
		 lookup of client_addr. This field will only be non-null for 
		 IP connections, and only when log_hostname is enabled.
		 this maps to pg_stat_activity/client_hostname"
    ::= { statusEntry  8 }

clientPort OBJECT-TYPE
    SYNTAX	Integer32
    MAX-ACCESS  read-only
    STATUS	current
    DESCRIPTION "TCP port number that the client is using for communication with
		 this backend, or -1 if a Unix socket is used
		 this maps to pg_stat_activity/client_port"
    ::= { statusEntry  9 }

backendStart OBJECT-TYPE
    SYNTAX	OCTET STRING
    MAX-ACCESS  read-only
    STATUS	current
    DESCRIPTION "Time when this process was started, i.e., when the client 
		 connected to the server
		 this maps to pg_stat_activity/backend_start"
    ::= { statusEntry  10 }

transactionStart OBJECT-TYPE
    SYNTAX	OCTET STRING
    MAX-ACCESS  read-only
    STATUS	current
    DESCRIPTION "Time when this process' current transaction was started, 
		 or null if no transaction is active. If the current query
		 is the first of its transaction, this column is equal to
		 the query_start column.
		 this maps to pg_stat_activity/xact_start"
    ::= { statusEntry  11 }

queryStart OBJECT-TYPE
    SYNTAX	OCTET STRING
    MAX-ACCESS  read-only
    STATUS	current
    DESCRIPTION "Time when the currently active query was started, or if
		 state is not active, when the last query was started
		 this maps to pg_stat_activity/query_start"
    ::= { statusEntry  12 }

stateChange OBJECT-TYPE
    SYNTAX	OCTET STRING
    MAX-ACCESS  read-only
    STATUS	current
    DESCRIPTION "Time when the state was last changed
		 this maps to pg_stat_activity/state_change"
    ::= { statusEntry  13 }

waiting OBJECT-TYPE
    SYNTAX	OCTET STRING
    MAX-ACCESS  read-only
    STATUS	current
    DESCRIPTION "True if this backend is currently waiting on a lock
		 this maps to pg_stat_activity/waiting"
    ::= { statusEntry  14 }

state OBJECT-TYPE
    SYNTAX	OCTET STRING
    MAX-ACCESS  read-only
    STATUS	current
    DESCRIPTION "Current overall state of this backend. Possible values are:
		     active:  The backend is executing a query.
		     idle:    The backend is waiting for a new client command.
		     idle in transaction: 
			The backend is in a transaction, but is not currently
			executing a query.
		     idle in transaction (aborted):
			This state is similar to idle in transaction, except
			one of the statements in the transaction caused an error.
		     fastpath function call: 
			The backend is executing a fast-path function.
		     disabled: 
			This state is reported if track_activities is 
			disabled in this backend.
		 this maps to pg_stat_activity/state"
    ::= { statusEntry  15 }

query OBJECT-TYPE
    SYNTAX	OCTET STRING
    MAX-ACCESS  read-only
    STATUS	current
    DESCRIPTION "Text of this backend's most recent query. If state is active
		 this field shows the currently executing query. In all 
		 other states, it shows the last query that was executed.
		 this maps to pg_stat_activity/query"
    ::= { statusEntry  16 }



END
--vim set ts=4 sw=4
