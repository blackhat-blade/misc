SMCA-TEST-ONE-MIB DEFINITIONS ::= BEGIN

--
-- 1.3.6.1.4.1.45204.0.0.2.1
--

IMPORTS
    MODULE-IDENTITY, OBJECT-TYPE, Integer32 FROM SNMPv2-SMI
    OBJECT-GROUP                  	    FROM SNMPv2-CONF
--    InetAddressType, InetAddress            FROM INET-ADDRESS-MIB
;

smcaTestOne MODULE-IDENTITY
    LAST-UPDATED "201502220000Z"
   
     
    ORGANIZATION "smca"
    CONTACT-INFO "email: nobody@sanemail.de"
    DESCRIPTION  "Test MIB"
    REVISION "201502220000Z"
    DESCRIPTION  "First draft"
    ::= { iso(1) org(3) dod(6) internet(1) private(4) enterprises(1) fourhorsemen(45204) sub(1) smca(1) management(2) mibs(2) 1 }


--testOneGroup OBJECT-GROUP
--	OBJECTS 
--	{
--		testOneInteger
--	}
--	STATUS      current
--	DESCRIPTION "Group 1 - an object group"
--		::= {smcaTestOne groups(1) 1}


--# testOneScalars OBJECT IDENTIFIER ::= { smcaTestOne items(2) 1 }
--
-- Example scalars
--
testOneInteger OBJECT-TYPE
    SYNTAX      Integer32
    MAX-ACCESS  read-write
    STATUS      current
    DESCRIPTION
	"This is a simple object which merely houses a writable
	 integer.  It's only purposes is to hold the value of a single
	 integer.  Writing to it will simply change the value for
	 subsequent GET/GETNEXT/GETBULK retrievals.

	 This example object is implemented in the
	 agent/mibgroup/examples/scalar_int.c file."
   -- DEFVAL { 42 }
    ::= { smcaTestOne types(3) 1 }
END
